Fault-Injection-Messages DEFINITIONS AUTOMATIC TAGS ::= 
BEGIN
  -- ---
  -- ENUMERATED
  -- ---

  MaskOperationASN ::= ENUMERATED {
    setOperation, xorOperation, orOperation
  }

  ExchangeStatusEnumASN ::= ENUMERATED {
    waitingConf, sendingActions, actionsReceived
  }

  -- ---
  -- SEQUENCE
  -- ---

  ExchangeStatusASN ::= SEQUENCE {
    status                      ExchangeStatusEnumASN
  }

  RegisterInjectionActionASN ::= SEQUENCE {
    injectionAddress            INTEGER(0..4294967295),
    registerIndex               INTEGER(0..15),           -- R0, R1..R12, SP, LR, PC
    valueMask                   INTEGER(0..4294967295),
    omitCallsNumber             INTEGER(0..4294967295),
    maskOperation               MaskOperationASN
  }

  MemoryInjectionActionASN ::= SEQUENCE {
    injectionAddress            INTEGER(0..4294967295),
    memoryAddress               INTEGER(0..4294967295),
    valueMask                   INTEGER(0..4294967295),
    omitCallsNumber             INTEGER(0..4294967295),
    maskOperation               MaskOperationASN
  }

  InjectionActionChoiceASN ::= CHOICE {
    registerAction              RegisterInjectionActionASN,
    memoryAction                MemoryInjectionActionASN
  }

  InjectionActionASN ::= SEQUENCE {
    injectionAction             InjectionActionChoiceASN,
    injectionActionIndex        INTEGER(0..4294967295)
  }

  InjectionConfigurationASN ::= SEQUENCE {
    logging                     BOOLEAN,
    injectionActionsNum         INTEGER(0..4294967295),
    registerInjectionActionsNum INTEGER(0..4294967295),
    memoryInjectionActionsNum   INTEGER(0..4294967295)
  }

  LogMsgASN ::= SEQUENCE {
  }

  LogIntValueASN ::= SEQUENCE {
    intValue                   INTEGER(0..4294967295)
  }

  LogStringValueASN ::= SEQUENCE {
    stringValue                OCTET STRING (SIZE(128))
  }

  LogChoiceASN ::= CHOICE {
    logMsg                     LogMsgASN,
    logIntValue                LogIntValueASN,
    logStringValue             LogStringValueASN
  }

  LogASN ::= SEQUENCE {
    logDescription             OCTET STRING (SIZE(128)),
    logChoice                  LogChoiceASN,
    logIndex                   INTEGER(0..4294967295)
  }

END
