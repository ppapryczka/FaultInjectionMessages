Fault-Injection-Messages DEFINITIONS AUTOMATIC TAGS ::= 
BEGIN

  MaskOperation ::= ENUMERATED {
    setOperation, xorOperation, orOperation
  }

  ExchangeStatusEnum ::= ENUMERATED {
    waitingConf, sendingActions, actionsReceived
  }

  ExchangeStatus ::= SEQUENCE {
    status                      ExchangeStatusEnum
  }

  RegisterInjectionAction ::= SEQUENCE {
    injectionAddress            INTEGER(0..4294967295),
    registerIndex               INTEGER(0..15),           -- R0, R1..R12, SP, LR, PC
    valueMask                   INTEGER(0..4294967295),
    omitCallsNumber             INTEGER(0..4294967295),
    maskOperation               MaskOperation
  }

  MemoryInjectionAction ::= SEQUENCE {
    injectionAddress            INTEGER(0..4294967295),
    memoryAddress               INTEGER(0..4294967295),
    valueMask                   INTEGER(0..4294967295),
    omitCallsNumber             INTEGER(0..4294967295),
    maskOperation               MaskOperation
  }

  InjectionActionChoice ::= CHOICE {
    registerAction              RegisterInjectionAction,
    memoryAction                MemoryInjectionAction
  }

  InjectionAction ::= SEQUENCE {
    injectionAction             InjectionActionChoice,
    injectionActionIndex        INTEGER(0..4294967295)
  }

  InjectionConfiguration ::= SEQUENCE {
    logging                     BOOLEAN,
    injectionActionsNum         INTEGER(0..4294967295),
    registerInjectionActionsNum INTEGER(0..4294967295),
    memoryInjectionActionsNum   INTEGER(0..4294967295)
  }
END
